# coding: utf-8

import FreeCAD as App
import FreeCADGui as Gui
import Draft

# Gt active document
doc = App.activeDocument()

# Get selection
s = Gui.Selection.getSelectionEx()

# Make a facebinder of the selection
facebinder = Draft.makeFacebinder(s)

# Recompute
doc.recompute()

# Create a sketch from facebinder
sk = Draft.makeSketch(facebinder, autoconstraints=True, delete=True)

# Recompute
doc.recompute()

# Reset placement of sketch so it's on XY plane
sk.Placement=App.Placement(App.Vector(0,0,0), App.Rotation(App.Vector(0,0,1),0))

# Make draft object with geom from sketch
drafty = Draft.draftify(sk, makeblock=False, delete=True)

# Create a group for draft geom
group = doc.addObject('App::DocumentObjectGroup','ToSVG')

# Make drafty a list if it is not already
if not isinstance(drafty, list):
    drafty = [drafty]

# For each geom of the sketch, set MakeFace to false and add it in group
for geom in drafty:
    group.addObject(geom)
    if hasattr(geom, 'MakeFace'):
        geom.MakeFace = False

# Recompute
doc.recompute()
Gui.Selection.clearSelection()
Gui.Selection.addSelection(doc.Name,group.Name)
Gui.activateWorkbench("DraftWorkbench")
App.DraftWorkingPlane.alignToPointAndAxis(FreeCAD.Vector(0.0, 0.0, 0.0), FreeCAD.Vector(0, 0, 1), 0.0)
